module diag-agent-alarm-types {
  yang-version 1.1;
  namespace "urn:example:yang:diag-agent-alarm-types";
  prefix daat;

  import ietf-alarms {
    prefix al;
  }

  organization
    "optical-network-anomaly-aiops";
  contact
    "diag_agent maintainers";
  description
    "Alarm type identities (RFC 8632 alarm-type-id) for the test bed's
     alarm catalogue, so that ietf-incident alarm events can carry
     'alarm-type-id' as a valid identityref.

     The full module is generated by semantic_memory/loaders/catalog_to_rdf.py
     from kg_lib/alarm_catalog_9800.json (one identity per alarm name,
     grouped under a per-layer base).  This excerpt lists the alarm types
     documented in kb-fault-modes.ttl.";

  revision 2026-11-02 {
    description
      "Excerpt for the design documents.";
  }

  identity optical-alarm {
    base al:alarm-type-id;
    description
      "Base of all test-bed alarm types.";
  }

  identity ots-layer {
    base optical-alarm;
  }
  identity och-layer {
    base optical-alarm;
  }
  identity otu-layer {
    base optical-alarm;
  }
  identity odu-layer {
    base optical-alarm;
  }
  identity sdh-layer {
    base optical-alarm;
  }
  identity equipment {
    base optical-alarm;
  }
  identity environment {
    base optical-alarm;
  }

  identity OTS_LOS {
    base ots-layer;
    description
      "OTS loss of signal.";
  }
  identity MUT_LOS {
    base ots-layer;
    description
      "Multiplexed signal loss of signal.";
  }
  identity IN_PWR_LOW {
    base ots-layer;
  }
  identity IN_PWR_ABN {
    base ots-layer;
  }
  identity R_LOS {
    base och-layer;
    description
      "Receive-side loss of signal.";
  }
  identity OTU_SSF {
    base otu-layer;
    description
      "OTU server signal fail.";
  }
  identity OTU_BDI {
    base otu-layer;
    description
      "OTU backward defect indication.";
  }
  identity OTU_DEG {
    base otu-layer;
  }
  identity OTU_TIM {
    base otu-layer;
  }
  identity BEFFEC_EXC {
    base otu-layer;
  }
  identity ODU_PM_SSF {
    base odu-layer;
    description
      "ODU path-monitoring server signal fail.";
  }
  identity OPU_PLM {
    base odu-layer;
  }
  identity B1_EXC {
    base sdh-layer;
  }
  identity B2_EXC {
    base sdh-layer;
  }
  identity BD_OFFLINE {
    base equipment;
  }
  identity HARD_BAD {
    base equipment;
  }
  identity POWER_ABNORMAL {
    base equipment;
  }
  identity FAN_FAIL {
    base environment;
  }
  identity TEMP_OVER {
    base environment;
  }
}
